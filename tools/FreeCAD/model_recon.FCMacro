import itertools
import json
import numpy as np

try:
    import Part
    import Mesh
    import Draft
    import Arch
    import BOPTools.JoinFeatures
    import ifcopenshell
    import exportIFC
    import importOBJ
    import FreeCADGui
except ImportError as e:
    print('FreeCAD is not available, running standalone.')
    print(e)


def check_intersection(object_1, object_2):
    """check for intersection between two objects in FreeCAD"""
    shape_1 = object_1.Shape
    shape_2 = object_2.Shape

    # check for intersection
    common_shape = shape_1.common(shape_2)

    if common_shape.Volume > 1e-6\
            and common_shape.Area > 1e-6\
            and common_shape.Length > 1e-6:
        return True
    else:
        return False



if __name__ == '__main__':

    try:
        App = FreeCAD
        # close all documents
        open_docs = App.listDocuments().keys()
        for doc in open_docs:
            App.closeDocument(doc)
    except NameError as e:
        print('FreeCAD is not available, running standalone.')
        print(e)

    path_local = '/Users/fnoic/PycharmProjects/reconstruct/'
    path_config = 'config_reconstruct_a.json'
    # load yaml file content
    config = json.load(open(path_local + path_config, 'r'))

    with open(path_local + config['path_skeleton'], 'rb') as f:
        skeleton_dict = json.load(f)
        # print(skeleton_dict)
        # skeleton = pickle.load(f)
        # print(skeleton.bones)

    try:
        App.newDocument(config['export_filename'])
        # fcdocexport = App.getDocument(config['export_filename'])
        # fcdocexport.addObject('PartDesign::Body', 'Body')
        fcdoc = App.getDocument(config['export_filename'])
        body = fcdoc.addObject('PartDesign::Body', 'Body')
    except Exception as e:
        print('FreeCAD is not available, running standalone.')
        print(e)

    cs_area = {}
    for bone_flag in skeleton_dict.keys():
        bone_id = int(bone_flag.split('_')[1])
        bone = skeleton_dict[bone_flag]
        # cs vertices
        beam_verts = np.asarray(bone['beam_verts'])

        area_x = beam_verts[6, 0] - beam_verts[0, 0]
        area_y = beam_verts[6, 1] - beam_verts[0, 1]
        area = area_x * area_y
        cs_area[bone_id] = area

        # center vertices around origin = bone.line_cog_...
        delta_x = beam_verts[0, 0] + (np.max(beam_verts[:, 0] - np.min(beam_verts[:, 0])) / 2)
        delta_y = beam_verts[0, 1] + (np.max(beam_verts[:, 1] - np.min(beam_verts[:, 1])) / 2)
        beam_verts[:, 0] -= delta_x
        beam_verts[:, 1] -= delta_y
        beam_verts = np.hstack((beam_verts, np.zeros((beam_verts.shape[0], 1))))
        # rotation matrix
        rot_mat = np.asarray(bone['rot_mat'])
        z_angle_add = bone['angle_xy']
        # define rotation matrix for z axis rotation
        rot_mat_z = np.asarray([[np.cos(z_angle_add), -np.sin(z_angle_add), 0],
                                [np.sin(z_angle_add), np.cos(z_angle_add), 0],
                                [0, 0, 1]])
        # multiply rotation matrices
        rot_mat = np.dot(rot_mat.T, rot_mat_z)

        rot_mat = np.asarray(bone['rot_mat'])
        z_angle_add = bone['angle_xy']
        rot_mat_z = np.asarray([[np.cos(z_angle_add), -np.sin(z_angle_add), 0],
                                [np.sin(z_angle_add), np.cos(z_angle_add), 0],
                                [0, 0, 1]])
        rot_mat = np.dot(rot_mat_z, rot_mat)


        # create placement
        try:
            pl = FreeCAD.Placement()
            pl.Base = FreeCAD.Vector(bone['start'][0], bone['start'][1], bone['start'][2])
            pl.Rotation = FreeCAD.Rotation(rot_mat[0][0], rot_mat[0][1], rot_mat[0][2],
                                           rot_mat[1][0], rot_mat[1][1], rot_mat[1][2],
                                           rot_mat[2][0], rot_mat[2][1], rot_mat[2][2])
            fcdoc.recompute()



            # create bone line
            vector = np.asarray([bone['end'][i] - bone['start'][i] for i in range(3)])
            length = np.linalg.norm(vector)
            points = [FreeCAD.Vector(bone['start'][0], bone['start'][1], bone['start'][2]),
                      FreeCAD.Vector(bone['end'][0], bone['end'][1], bone['end'][2])]
            line = Draft.make_wire(points, placement=pl, closed=False, face=True, support=None)
            Draft.autogroup(line)
            fcdoc.recompute()

            # create offset on yz plane with x coordinate of midpoint + rotated plane
            point = FreeCAD.ActiveDocument.addObject("Part::Vertex", f"Point{bone_id}")
            point.X = bone['start'][0]
            point.Y = bone['start'][1]
            point.Z = bone['start'][2]

            # create cross-section
            fcdoc.getObject('Body').newObject('Sketcher::SketchObject', f'cross_section{bone_id}')
            polygon = fcdoc.getObject(f'cross_section{bone_id}')
            # polygon.Support = (fcdoc.getObject(f'DatumPlane{bone_id}'), [''])
            polygon.MapMode = 'FlatFace'
            polygon_edges = []
            for i in range(len(beam_verts)):
                if i != len(beam_verts) - 1:
                    polygon_edges.append((i, i + 1))
                else:
                    polygon_edges.append((i, 0))

            for edge in polygon_edges:
                polygon.addGeometry(Part.LineSegment(
                    App.Vector(beam_verts[edge[0]][0], beam_verts[edge[0]][1], beam_verts[edge[0]][2]),
                    App.Vector(beam_verts[edge[1]][0], beam_verts[edge[1]][1], beam_verts[edge[1]][2])),
                    False
                )
            polygon.Placement = pl
            Draft.autogroup(polygon)
            fcdoc.recompute()
            #
            # execute sweep operation
            fcdoc.addObject('Part::Sweep', f'beam{bone_id}')
            sweep = fcdoc.getObject(f'beam{bone_id}')
            sweep.Sections = polygon
            sweep.Spine = line
            sweep.Solid = True
            sweep.Frenet = False

            # remove the polygon from the body
            fcdoc.getObject('Body').removeObject(polygon)


            # old = polygon.getParentGeoFeatureGroup()
            # old.removeObject(polygon)
            # fcdoc.getObject(f'beam{bone_id}').addObject(polygon)
            # # sweep.addObject(polygon)
            fcdoc.recompute()

        except Exception as e:
            print('FreeCAD is not available, running standalone.')
            print(e)

    # raise Exception('stop here')

    # calculate area of cross-section for each bone (box 0::6)
    connection_candidates = cs_area.keys()
    keepers = [f'beam{item}' for item in connection_candidates]
    # sort by area
    connection_candidates_sorted = sorted(connection_candidates, key=lambda x: cs_area[x], reverse=True)
    connection_candidates_paired = list(itertools.combinations(connection_candidates_sorted, 2))
    connection_mask = np.zeros(len(connection_candidates_paired), dtype=bool)

    for i, connection in enumerate(connection_candidates_paired):
        if check_intersection(fcdoc.getObject(f'beam{connection[0]}'), fcdoc.getObject(f'beam{connection[1]}')):
            connection_mask[i] = True

    connection_candidates_paired = [connection_candidates_paired[i] for i in range(len(connection_candidates_paired)) if connection_mask[i]]
    print(f'connection_candidates_paired = {connection_candidates_paired}')

    compounds = {}
    compound_key = 0

    max = 19 ### for testing purposes TODO remove

    for iter, connection_candidate in enumerate(connection_candidates_paired):

        previously_involved = []
        purge_from_compounds = []

        if iter > max:
            break
        if not any(connection_candidate[0] in lst for lst in compounds.values()):
            previously_involved.extend([connection_candidate[0]])
            name_1 = f'beam{connection_candidate[0]}'
            obj_1 = fcdoc.getObject(name_1)
            # print(f'not connected, {name_1}')
        else:
            for key, lst in compounds.items():
                if connection_candidate[0] in lst:
                    compound_id = key
                    break
            previously_involved.extend(compounds[compound_id])
            purge_from_compounds.append(compound_id)
            name_1 = f'compound{compound_id}'
            obj_1 = fcdoc.getObject(name_1)
            # print(f'aggregate {name_1} includes beam{connection_candidate[0]}')

        if not any(connection_candidate[1] in lst for lst in compounds.values()):
            previously_involved.extend([connection_candidate[1]])
            name_2 = f'beam{connection_candidate[1]}'
            obj_2 = fcdoc.getObject(name_2)
            # print(f'not connected, {name_2}')
        else:
            for key, lst in compounds.items():
                if connection_candidate[1] in lst:
                    compound_id = key
                    break
            previously_involved.extend(compounds[compound_id])
            purge_from_compounds.append(compound_id)
            name_2 = f'compound{compound_id}'
            obj_2 = fcdoc.getObject(name_2)
            # print(f'aggregate {name_2} includes beam{connection_candidate[1]}')

        if name_1 == name_2:
            print(f'---> connection candidate {connection_candidate[0]} and {connection_candidate[1]} are already in the same compound')
            continue

        print(f'-  intersection between {name_1} and {name_2}')
        compound_key += 1

        # create the compound object from the intersecting objects
        name_3 = f'compound{compound_key}'
        j = BOPTools.JoinFeatures.makeConnect(name=name_3)
        j.Objects = [obj_1, obj_2]
        j.Proxy.execute(j)
        j.purgeTouched()
        for obj in j.ViewObject.Proxy.claimChildren():
            obj.ViewObject.hide()

        print(f'-- created {name_3}')
        try:
            keepers.extend([name_3])
        except ValueError as e:
            print(e)

        print(f'####!! {keepers}')

        # remove name_1 and name_2 from keepers
        try:
            keepers.remove(name_1)
            print(f'###### removed {name_1} from keepers')
        except ValueError as e:
            print(e)
        try:
            keepers.remove(name_2)
            print(f'###### removed {name_2} from keepers')
        except ValueError as e:
            print(e)

        # delete obj_1 and obj_2

        # print(f'remoing {obj_1.Name} and {obj_2.Name} from the document')
        # fcdoc.removeObject(obj_1.Name)
        # fcdoc.removeObject(obj_2.Name)


        # # add the compound object
        # compound_obj = fcdoc.addObject("Part::Feature", f"compound{compound_key}")
        # compound_obj.Shape = compound
        #
        # map the new compound to both candidates
        if compound_key not in compounds.keys():
            compounds[compound_key] = []
        compounds[compound_key] = previously_involved

        # TODO: find why keepers isn't complete

        # remove the purged compounds
        print(f'to purge: {purge_from_compounds}')
        for item in purge_from_compounds:
            compounds.pop(item)


        # Recompute the document to update the compound
        fcdoc.recompute()

        print(f'-->{compounds}\n')



    print('done')
    print(f'exporting keepers: {keepers}')

    # export as obj
    __objs__ = []
    for keeper in keepers:
        __objs__.append(fcdoc.getObject(keeper))

    importOBJ.export(__objs__, path_local + config['export_filename'] + '.obj')

    # export as ifc
    if hasattr(exportIFC, "exportOptions"):
        options = exportIFC.exportOptions(f'{path_local}{config["export_filename"]}.ifc')
        exportIFC.export(__objs__, options)
    else:
        exportIFC.export(__objs__, f'{path_local}{config["export_filename"]}.ifc')

    del __objs__

    FreeCADGui.ActiveDocument.ActiveView.fitAll()
    FreeCADGui.SendMsgToActiveView("ViewFit")
    FreeCADGui.activeDocument().activeView().viewAxometric()
