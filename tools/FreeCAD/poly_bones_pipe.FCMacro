import os
import stat
import pickle

import numpy as np
from sys import platform

import Part
import Mesh
import importOBJ
import Draft
from numpy.linalg import norm


def quaternion_rotation(v, ax=np.array([1.0, 0.0, 0.0])):
    v = v / norm(v)  # Normalize the vector

    if v[0] == 1.0:  # Vector is already aligned with x-axis
        q = np.array([1.0, 0.0, 0.0, 0.0])
    else:
        axis = np.cross(v, ax)  # Calculate rotation axis
        angle = np.arccos(np.dot(v, ax))  # Calculate rotation angle
        q = np.array([np.cos(angle/2), axis[0]*np.sin(angle/2), axis[1]*np.sin(angle/2), axis[2]*np.sin(angle/2)])  # Convert axis-angle representation to quaternion

    return q


def sketch_bone(objlines):
    start = objlines[0].split(' ')[1:4]
    end = objlines[1].split(' ')[1:4]

    x_start = float(start[0])
    y_start = float(start[1])
    z_start = float(start[2])
    x_end = float(end[0])
    y_end = float(end[1])
    z_end = float(end[2])

    return {
        'start': (x_start, y_start, z_start),
        'end': (x_end, y_end, z_end)
    }


def bone_pose(bone):
    x_start = bone['start'][0]
    y_start = bone['start'][1]
    z_start = bone['start'][2]
    x_end = bone['end'][0]
    y_end = bone['end'][1]
    z_end = bone['end'][2]

    array = np.array([
        [x_start, y_start, z_start],
        [x_end, y_end, z_end]
    ])
    translate_start = np.array([x_start, y_start, z_start])
    translate_end = np.array([x_end - x_start, y_end - y_start, z_end - z_start])

    len_bone = np.linalg.norm(translate_end)
    ax_bone = np.array([len_bone, 0, 0])
    a = ax_bone / np.linalg.norm(ax_bone)
    b = translate_end / np.linalg.norm(translate_end)

    # calculate rotation matrix from ax_bone to translate_end
    v = np.cross(a, b)
    s = np.linalg.norm(v)
    c = np.dot(a, b)
    vx = np.array([
        [0, -v[2], v[1]],
        [v[2], 0, -v[0]],
        [-v[1], v[0], 0]
    ])
    rot_mat = np.eye(3) + vx + np.dot(vx, vx) * ((1 - c) / (s ** 2))

    # apply rotation matrix to ax_bone
    translate_end_nu = np.dot(rot_mat, ax_bone)

    bone['rotation'] = rot_mat
    bone['translate_start'] = translate_start
    bone['translate_end'] = translate_end
    bone['ax_bone'] = ax_bone

    return bone


if __name__ == '__main__':

    ids = [i for i in range(1, 30)]
    segments = [f'intermediate_bone_{i}.obj' for i in ids]

    # for linefile, no in zip(segments, ids):
    #
    #     if platform == 'darwin':
    #         path_1 = f'/Users/fnoic/PycharmProjects/reconstruct/data/first_beam.txt'
    #         path_2 = f'/Users/fnoic/PycharmProjects/reconstruct/data/out/0_skeleton/{linefile}'
    #         path_3 = f'/Users/fnoic/PycharmProjects/reconstruct/data/out/beam_{no}/rotations.pickle'
    #         path_4 = f'/Users/fnoic/PycharmProjects/reconstruct/data/out/0_skeleton/beam_bone_{linefile}.obj'
    #         # os.chmod(f'/Users/fnoic/PycharmProjects/reconstruct/data/out/0_skeleton/', stat.S_IRWXO)
    #         # os.chmod(f'/Users/fnoic/PycharmProjects/reconstruct/data/out/0_skeleton/', stat.S_IRWXU)
    #         # os.chmod(f'/Users/fnoic/PycharmProjects/reconstruct/data/out/0_skeleton/', stat.S_IRWXG)
    #     # not sure if this is stable
    #     # elif platform == 'win32':
    #     #     path_1 = f'D:/Uni/hiwi/reconstruct/data/first_beam.txt'
    #     #     path_2 = f'D:/Uni/hiwi/reconstruct/data/out/0_skeleton/{linefile}'
    #     #     path_3 = f'D:/Uni/hiwi/reconstruct/data/out/beam_{no}/rotations.pickle'
    #     #     path_4 = f'D:/Uni/hiwi/reconstruct/data/out/0_skeleton/beam_bone_{linefile}.obj'
    #     else:
    #         path_0 = f'C:/Users/ga25mal/PyCharmProjects/reconstruct/data/out_pipe/'
    #         path_hack = f'C:/Users/ga25mal/PyCharmProjects/reconstruct/data/out_pipe/sweep_pipe.txt'

        # hardcode_path as FC macro works on different directories and I don't care
        # TODO: the following is an attempt to robustly load the objs while identifying the passing, connected pipes. for now cardcoded
        # dict = {}
        # for objfile in os.listdir(path_0):
        #     if objfile.endswith('obj'):
        #         inst_l0 = objfile[10]
        #         inst_l1 = objfile[17]
        #         with open(path_0 + objfile, 'r') as f:
        #             # read obj file
        #             objlines = f.readlines()
        #             # read x y z as floats
        #             x0, y0, z0 = [float(i) for i in objlines[0].split(' ')[1:4]]
        #             x1, y1, z1 = [float(i) for i in objlines[1].split(' ')[1:4]]
        #             lr = [inst_l1, [x0, y0, z0], [x1, y1, z1]]
        #             if inst_l0 in dict:
        #                 dict[inst_l0].append(lr)
        #             else:
        #                 dict[inst_l0] = [lr]

    path_hack = f'D:/Uni/hiwi/reconstruct/data/out_pipe/sweep_pipe.txt'

    piperuns = []
    with open(path_hack, 'r') as f:
        # read obj file
        objlines = f.readlines()
        # read x y z as floats
        piperun_0 = [[float(i) for i in objlines[0].split(' ')[1:7]],
                     [float(i) for i in objlines[1].split(' ')[1:7]],
                     [float(i) for i in objlines[2].split(' ')[1:7]]]
        piperuns.append(piperun_0)
        piperun_1 = [[float(i) for i in objlines[3].split(' ')[1:7]]]
        piperuns.append(piperun_1)
        piperun_2 = [[float(i) for i in objlines[4].split(' ')[1:7]]]
        piperuns.append(piperun_2)

    radius = 17.7 /100  # sorry.

    # 3 set up FreeCAD "file"
    App = FreeCAD
    filename = 'pipe_skeleton'
    App.newDocument(filename)
    fcdoc = App.getDocument(filename)
    fcdoc.addObject('PartDesign::Body', 'Body')
    fcdoc.recompute()

    for i, piperun in enumerate(piperuns):
        print(i)
        # 4 draw wire in Draft
        pl = FreeCAD.Placement()
        # pl.Rotation.Q = (0.0, 0.0, 0.0, 1.0)
        pl.Base = FreeCAD.Vector(piperun[0][0], piperun[0][1], piperun[0][2])
        if len(piperun) == 1:
            points = [
                FreeCAD.Vector(piperun[0][0], piperun[0][1], piperun[0][2]),
                FreeCAD.Vector(piperun[0][3], piperun[0][4], piperun[0][5])]
            print(points)
        if len(piperun) == 3:  # again, I am very sorry for this hack
            points = [
                FreeCAD.Vector(piperun[0][0], piperun[0][1], piperun[0][2]),
                FreeCAD.Vector(piperun[0][3], piperun[0][4], piperun[0][5]),
                FreeCAD.Vector(piperun[1][0], piperun[1][1], piperun[1][2]),
                FreeCAD.Vector(piperun[1][3], piperun[1][4], piperun[1][5]),
                FreeCAD.Vector(piperun[2][0], piperun[2][1], piperun[2][2]),
                FreeCAD.Vector(piperun[2][3], piperun[2][4], piperun[2][5])]
        line = Draft.make_wire(points, placement=pl, closed=False, face=True, support=None)
        Draft.autogroup(line)
        FreeCAD.ActiveDocument.recompute()

        pl = FreeCAD.Placement()

        # calculate rotation matrix to rotate z axis with vector
        vector = np.array(
            points[1] - points[0]
        )
        # vector = np.array([0, 0, 1])
        # if i == 0:
        #     axis = np.array([0, 1, 0])
        #     q = quaternion_rotation(v=vector, ax=axis)
        # else:
        #     q = quaternion_rotation(v=vector)
        # q = quaternion_rotation(v=vector)


        # pl.Rotation.Q=(q[0], q[1], q[2], q[3])

        a = np.array([0, 0, 1])
        b = vector / np.linalg.norm(vector)
        v = np.cross(a, b)
        c = np.dot(a, b)
        s = np.linalg.norm(v)
        kmat = np.array([[0, -v[2], v[1]],
                         [v[2], 0, -v[0]],
                         [-v[1], v[0], 0]])
        rotmat = np.eye(3) + kmat + kmat.dot(kmat) * ((1 - c) / (s ** 2))
        # rotmat from numpy to FreeCAD
        rotmat = App.Matrix(rotmat[0][0], rotmat[0][1], rotmat[0][2], 0,
                            rotmat[1][0], rotmat[1][1], rotmat[1][2], 0,
                            rotmat[2][0], rotmat[2][1], rotmat[2][2], 0,
                            0, 0, 0, 1)

        pl.Rotation.Matrix = rotmat

        pl.Base = FreeCAD.Vector(piperun[0][0], piperun[0][1], piperun[0][2])
        circle = Draft.makeCircle(radius=radius, placement=pl, face=True, support=None)
        Draft.autogroup(circle)
        FreeCAD.ActiveDocument.recompute()
        #
        # 5 make pipe
        App.getDocument(filename).addObject('Part::Sweep', f'Pipe_{i}')
        App.getDocument(filename).ActiveObject.Sections = [circle, ]
        App.getDocument(filename).ActiveObject.Spine = line
        App.getDocument(filename).ActiveObject.Solid = True
        App.getDocument(filename).ActiveObject.Frenet = False
        App.getDocument(filename).ActiveObject.Transition = u"Round corner"


    olddoc=FreeCAD.ActiveDocument
    App = FreeCAD
    filename = 'ifc_pips'
    App.newDocument(filename)
    fcdoc = App.getDocument(filename)

    for obj in olddoc.Objects:
        if obj.TypeId=='Part::Sweep':
            placement=obj.Placement
            crosssection=fcdoc.copyObject(obj.Sections[0], True)
            line=fcdoc.copyObject(obj.Spine[0],True)
            pipe = Arch.makePipe(crosssection)
            Draft.autogroup(pipe)
            pipe = Arch.makePipe(line)
            Draft.autogroup(pipe)
            pipe.Diameter=radius*2

    print('PyCharm says hi and congrats for running the whole macro without errors!')
